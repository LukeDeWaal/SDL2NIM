DV DEFINITIONS ::=

BEGIN

MyInt ::= INTEGER (0..255)

MyInteger ::= INTEGER (-16384 .. 16383)

MyBool ::= BOOLEAN

MyEnum ::= ENUMERATED { hello, world }

MySeq ::= SEQUENCE {
   a MyInt,
   b MyBool,
   c MyEnum
}

END
